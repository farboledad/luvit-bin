-- OPTION-CLOUDGATE.mib - MIB for private Option CloudGate management objects.

OPTION-CLOUDGATE-MIB DEFINITIONS ::= BEGIN

IMPORTS

	enterprises, IpAddress
		FROM RFC1155-SMI
	DisplayString
		FROM RFC1213-MIB
	OBJECT-TYPE
		FROM RFC-1212;

option OBJECT IDENTIFIER
	::= { enterprises 21415 }

cloudGatePrivate OBJECT IDENTIFIER
	::= { option 0 }

systemInfo OBJECT IDENTIFIER ::= { cloudGatePrivate 0 }
primaryThreeGInterface OBJECT IDENTIFIER ::= { cloudGatePrivate 1 }
wlanAccesspoint OBJECT IDENTIFIER ::= { cloudGatePrivate 2 }

upTime OBJECT-TYPE
	SYNTAX DisplayString
	ACCESS read-only
	STATUS current
	DESCRIPTION
		"System up time"
	::= { systemInfo 0 }

hostName OBJECT-TYPE
	SYNTAX DisplayString
	ACCESS read-only
	STATUS current
	DESCRIPTION
		"Hostname"
	::= { systemInfo 1 }

currentTime OBJECT-TYPE
	SYNTAX DisplayString
	ACCESS read-only
	STATUS current
	DESCRIPTION
		"Current Time"
	::= { systemInfo 2 }

serialNumber OBJECT-TYPE
	SYNTAX DisplayString
	ACCESS read-only
	STATUS current
	DESCRIPTION
		"Serial Number of CloudGate"
	::= { systemInfo 3 }

sysLoad1 OBJECT-TYPE
	SYNTAX DisplayString
	ACCESS read-only
	STATUS current
	DESCRIPTION
		"System load for the last minute"
	::= { systemInfo 4 }

sysLoad5 OBJECT-TYPE
	SYNTAX DisplayString
	ACCESS read-only
	STATUS current
	DESCRIPTION
		"System load for the last 5 minutes"
	::= { systemInfo 5 }

sysLoad15 OBJECT-TYPE
	SYNTAX DisplayString
	ACCESS read-only
	STATUS current
	DESCRIPTION
		"System load for the last 15 minutes"
	::= { systemInfo 6 }

firmVer OBJECT-TYPE
	SYNTAX DisplayString
	ACCESS read-only
	STATUS current
	DESCRIPTION
		"CloudGate's firmware version"
	::= { systemInfo 7 }

AssociatedClients OBJECT-TYPE
	SYNTAX          Gauge32
	MAX-ACCESS      read-only
	STATUS          current
	DESCRIPTION
		"Number of clients currently associated with the access point"
	::= { wlanAccesspoint 0 }

ClientAssociations OBJECT-TYPE
	SYNTAX          Counter32
	MAX-ACCESS      read-only
	STATUS          current
	DESCRIPTION
		"Historical number of client associations"
	::= { wlanAccesspoint 1 }

ClientDisassociations OBJECT-TYPE
	SYNTAX          Counter32
	MAX-ACCESS      read-only
	STATUS          current
	DESCRIPTION
		"Historical number of client disassociations"
	::= { wlanAccesspoint 2 }

ESSID OBJECT-TYPE
	SYNTAX          DisplayString
	MAX-ACCESS      read-only
	STATUS          current
	DESCRIPTION
		"WLAN access point SSID"
	::= { wlanAccesspoint 3 }

MAC OBJECT-TYPE
	SYNTAX          DisplayString
	MAX-ACCESS      read-only
	STATUS          current
	DESCRIPTION
		"WLAN MAC address"
	::= { wlanAccesspoint 4 }

Frequency OBJECT-TYPE
	SYNTAX          DisplayString
	MAX-ACCESS      read-only
	STATUS          current
	DESCRIPTION
		"WLAN frequency"
	::= { wlanAccesspoint 5 }

Channel OBJECT-TYPE
	SYNTAX          Integer32
	MAX-ACCESS      read-only
	STATUS          current
	DESCRIPTION
		"WLAN channel"
	::= { wlanAccesspoint 6 }

apn OBJECT-TYPE
	SYNTAX DisplayString
	ACCESS read-only
	STATUS current
	DESCRIPTION
		"Access Point Name"
	::= { primaryThreeGInterface 0 }

internetStatus OBJECT-TYPE
	SYNTAX DisplayString
	ACCESS read-only
	STATUS current
	DESCRIPTION
		"Internet Status"
	::= { primaryThreeGInterface 1 }

ipAddress OBJECT-TYPE
	SYNTAX DisplayString
	ACCESS read-only
	STATUS current
	DESCRIPTION
		"IP address"
	::= { primaryThreeGInterface 2 }

bCastAddress OBJECT-TYPE
	SYNTAX DisplayString
	ACCESS read-only
	STATUS current
	DESCRIPTION
		"Broadcast address"
	::= { primaryThreeGInterface 3 }

netMask OBJECT-TYPE
	SYNTAX DisplayString
	ACCESS read-only
	STATUS current
	DESCRIPTION
		"Network Mask"
	::= { primaryThreeGInterface 4 }

csRegistration OBJECT-TYPE
	SYNTAX DisplayString
	ACCESS read-only
	STATUS current
	DESCRIPTION
		"CS Registration"
	::= { primaryThreeGInterface 5 }

psRegistration OBJECT-TYPE
	SYNTAX DisplayString
	ACCESS read-only
	STATUS current
	DESCRIPTION
		"PS Registration"
	::= { primaryThreeGInterface 6 }

imei OBJECT-TYPE
	SYNTAX DisplayString
	ACCESS read-only
	STATUS current
	DESCRIPTION
		"IMEI"
	::= { primaryThreeGInterface 7 }

imsi OBJECT-TYPE
	SYNTAX DisplayString
	ACCESS read-only
	STATUS current
	DESCRIPTION
		"IMSI"
	::= { primaryThreeGInterface 8 }

firmMode OBJECT-TYPE
	SYNTAX DisplayString
	ACCESS read-only
	STATUS current
	DESCRIPTION
		"Firmware mode"
	::= { primaryThreeGInterface 9 }

carrier OBJECT-TYPE
	SYNTAX DisplayString
	ACCESS read-only
	STATUS current
	DESCRIPTION
		"Carrier"
	::= { primaryThreeGInterface 10 }

rssi OBJECT-TYPE
	SYNTAX Integer32
	ACCESS read-only
	STATUS current
	DESCRIPTION
		"RSSI"
	::= { primaryThreeGInterface 11 }

ecio OBJECT-TYPE
	SYNTAX DisplayString
	ACCESS read-only
	STATUS current
	DESCRIPTION
		"ECIO"
	::= { primaryThreeGInterface 12 }

bandClass OBJECT-TYPE
	SYNTAX DisplayString
	ACCESS read-only
	STATUS current
	DESCRIPTION
		"Band Class"
	::= { primaryThreeGInterface 13 }

serviceType OBJECT-TYPE
	SYNTAX DisplayString
	ACCESS read-only
	STATUS current
	DESCRIPTION
		"Service type"
	::= { primaryThreeGInterface 14 }

rfChannel OBJECT-TYPE
	SYNTAX DisplayString
	ACCESS read-only
	STATUS current
	DESCRIPTION
		"RF Channel"
	::= { primaryThreeGInterface 15 }

plmn OBJECT-TYPE
	SYNTAX DisplayString
	ACCESS read-only
	STATUS current
	DESCRIPTION
		"PLMN"
	::= { primaryThreeGInterface 16 }

csCellIDandLac OBJECT-TYPE
	SYNTAX DisplayString
	ACCESS read-only
	STATUS current
	DESCRIPTION
		"CS Cell ID and LAC"
	::= { primaryThreeGInterface 18 }

psCellIDandLac OBJECT-TYPE
	SYNTAX DisplayString
	ACCESS read-only
	STATUS current
	DESCRIPTION
		"PS Cell ID and LAC"
	::= { primaryThreeGInterface 19 }

pinStatus OBJECT-TYPE
	SYNTAX DisplayString
	ACCESS read-only
	STATUS current
	DESCRIPTION
		"PIN status"
	::= { primaryThreeGInterface 20 }

pinRetries OBJECT-TYPE
	SYNTAX DisplayString
	ACCESS read-only
	STATUS current
	DESCRIPTION
		"PIN retries"
	::= { primaryThreeGInterface 21 }

pukRetries OBJECT-TYPE
	SYNTAX DisplayString
	ACCESS read-only
	STATUS current
	DESCRIPTION
		"PUK retries"
	::= { primaryThreeGInterface 22 }

rxPackets OBJECT-TYPE
	SYNTAX DisplayString
	ACCESS read-only
	STATUS current
	DESCRIPTION
		"RX Packets"
	::= { primaryThreeGInterface 23 }

rxBytes OBJECT-TYPE
	SYNTAX DisplayString
	ACCESS read-only
	STATUS current
	DESCRIPTION
		"RX Bytes"
	::= { primaryThreeGInterface 24 }

txPackets OBJECT-TYPE
	SYNTAX DisplayString
	ACCESS read-only
	STATUS current
	DESCRIPTION
		"TX Packets"
	::= { primaryThreeGInterface 25 }

txBytes OBJECT-TYPE
	SYNTAX DisplayString
	ACCESS read-only
	STATUS current
	DESCRIPTION
		"TX Bytes"
	::= { primaryThreeGInterface 26 }

END
